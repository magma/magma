// Copyright 2020 The Magma Authors.
//
// This source code is licensed under the BSD-style license found in the
// LICENSE file in the root directory of this source tree.
//
// Unless required by applicable law or agreed to in writing, software
// distributed under the License is distributed on an "AS IS" BASIS,
// WITHOUT WARRANTIES OR CONDITIONS OF ANY KIND, either express or implied.
// See the License for the specific language governing permissions and
// limitations under the License.
//
module fbc-symphony-device {
    yang-version 1.1;
    namespace "http://facebook.com/yang/fbc-symphony/device";
    prefix dev;

    import ietf-yang-types {
        prefix yang;
    }

    import ietf-geo-location {
        prefix loc;
    }

    organization "Facebook, Inc.";

    contact "David Bond <davidmokonbond@fb.com>";

    description "This module defines basic information the Facebook
        Connectivity Platform might need to communicate about devices.";

    revision 2019-08-01 {
        description "Initial revision";
        reference "";
    }

    typedef status {
        type enumeration {
            enum UP {
                description "The agent is able to reach this device.";
            }
            enum DOWN {
                description "The agent is unable to reach this device.";
            }
        }

        description "A brief context about the state of the device as
                ascertained by the agent.";
    }

    container system {
        description "A container with generic system attributes.";

        leaf status {
            type status;
            description "A brief context about the state of the device as
                ascertained by the agent.";
        }

        leaf last-activity {
            type yang:timestamp;
            description "A timestamp giving the last known time when some
                action with this device was successful. This is given in seconds
                since the start of the Unix Epoch.";
        }

        uses loc:geo-location {
            refine geo-location/location {
                mandatory false;
            }
        }

        leaf venue {
            type string;
            description "A string identifier of the location this device is at.
                E.g. this could be a hotspot group.";
        }

        container latencies {
            description "Latencies related to this system.";

            list latency {
                key "type src dst";
                description "A list of latencies related to this system.";

                leaf rtt {
                    type uint64;
                    units usec;
                    description "The round trip time of this latency in
                        microseconds.";
                }

                leaf type {
                    type string;
                    description "A string defining the method used to measure
                        the latency (e.g. ping).";
                }

                leaf src {
                    type string;
                    description "A string defining the source of the latency
                        measurement";
                }

                leaf dst {
                    type string;
                    description "A string defining the destination of the
                        latency measurement";
                }
            }
        }
    }

    leaf-list errors {
        type string;
        description "A list of unstructured strings which contains errors
            received on this device. The time frame of these errors is not
            specified as neither is whether this is all the errors in a
            given timeframe.";
    }
}
