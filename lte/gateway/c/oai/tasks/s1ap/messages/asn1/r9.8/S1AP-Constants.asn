--
-- Licensed to the OpenAirInterface (OAI) Software Alliance under one or more
-- contributor license agreements.  See the NOTICE file distributed with
-- this work for additional information regarding copyright ownership.
-- The OpenAirInterface Software Alliance licenses this file to You under
-- the terms found in the LICENSE file in the root of this
-- source tree.
--
-- Unless required by applicable law or agreed to in writing, software
-- distributed under the License is distributed on an "AS IS" BASIS,
-- WITHOUT WARRANTIES OR CONDITIONS OF ANY KIND, either express or implied.
-- See the License for the specific language governing permissions and
-- limitations under the License.
---------------------------------------------------------------------------------
-- For more information about the OpenAirInterface (OAI) Software Alliance:
--      contact@openairinterface.org
--
-- **************************************************************
--
-- Constant definitions
--
-- **************************************************************

S1AP-Constants {
itu-t (0) identified-organization (4) etsi (0) mobileDomain (0)
eps-Access (21) modules (3) s1ap (1) version1 (1) s1ap-Constants (4) }

DEFINITIONS AUTOMATIC TAGS ::=

BEGIN

-- **************************************************************
--
-- IE parameter types from other modules.
--
-- **************************************************************

IMPORTS
    ProcedureCode,
    ProtocolIE-ID

FROM S1AP-CommonDataTypes;


-- **************************************************************
--
-- Elementary Procedures
--
-- **************************************************************

id-HandoverPreparation              ProcedureCode ::= 0
id-HandoverResourceAllocation       ProcedureCode ::= 1
id-HandoverNotification             ProcedureCode ::= 2
id-PathSwitchRequest                ProcedureCode ::= 3
id-HandoverCancel                   ProcedureCode ::= 4
id-E-RABSetup                       ProcedureCode ::= 5
id-E-RABModify                      ProcedureCode ::= 6
id-E-RABRelease                     ProcedureCode ::= 7
id-E-RABReleaseIndication           ProcedureCode ::= 8
id-InitialContextSetup              ProcedureCode ::= 9
id-Paging                           ProcedureCode ::= 10
id-downlinkNASTransport             ProcedureCode ::= 11
id-initialUEMessage                 ProcedureCode ::= 12
id-uplinkNASTransport               ProcedureCode ::= 13
id-Reset                            ProcedureCode::= 14
id-ErrorIndication                  ProcedureCode ::= 15
id-NASNonDeliveryIndication         ProcedureCode ::= 16
id-S1Setup                          ProcedureCode ::= 17
id-UEContextReleaseRequest          ProcedureCode ::= 18
id-DownlinkS1cdma2000tunneling      ProcedureCode ::= 19
id-UplinkS1cdma2000tunneling        ProcedureCode ::= 20
id-UEContextModification            ProcedureCode ::= 21
id-UECapabilityInfoIndication       ProcedureCode ::= 22
id-UEContextRelease                 ProcedureCode ::= 23
id-eNBStatusTransfer                ProcedureCode ::= 24
id-MMEStatusTransfer                ProcedureCode ::= 25
id-DeactivateTrace                  ProcedureCode ::= 26
id-TraceStart                       ProcedureCode ::= 27
id-TraceFailureIndication           ProcedureCode ::= 28
id-ENBConfigurationUpdate           ProcedureCode ::= 29
id-MMEConfigurationUpdate           ProcedureCode ::= 30
id-LocationReportingControl         ProcedureCode ::= 31
id-LocationReportingFailureIndication   ProcedureCode ::= 32
id-LocationReport                   ProcedureCode ::= 33
id-OverloadStart                    ProcedureCode ::= 34
id-OverloadStop                     ProcedureCode ::= 35
id-WriteReplaceWarning              ProcedureCode ::= 36
id-eNBDirectInformationTransfer     ProcedureCode ::= 37
id-MMEDirectInformationTransfer ProcedureCode ::= 38
id-PrivateMessage                   ProcedureCode ::= 39
id-eNBConfigurationTransfer         ProcedureCode ::= 40
id-MMEConfigurationTransfer         ProcedureCode ::= 41
id-CellTrafficTrace                 ProcedureCode ::= 42
id-Kill                             ProcedureCode ::= 43
id-downlinkUEAssociatedLPPaTransport    ProcedureCode ::= 44
id-uplinkUEAssociatedLPPaTransport      ProcedureCode ::= 45
id-downlinkNonUEAssociatedLPPaTransport ProcedureCode ::= 46
id-uplinkNonUEAssociatedLPPaTransport   ProcedureCode ::= 47

-- **************************************************************
--
-- Extension constants
--
-- **************************************************************

maxPrivateIEs                       INTEGER ::= 65535
maxProtocolExtensions               INTEGER ::= 65535
maxProtocolIEs                      INTEGER ::= 65535
-- **************************************************************
--
-- Lists
--
-- **************************************************************

maxNrOfCSGs                             INTEGER ::= 256
maxNrOfE-RABs                           INTEGER ::= 256
maxnoofTAIs                             INTEGER ::= 256
maxnoofTACs                             INTEGER ::= 256
maxNrOfErrors                           INTEGER ::= 256
maxnoofBPLMNs                           INTEGER ::= 6
maxnoofPLMNsPerMME                      INTEGER ::= 32
maxnoofEPLMNs                           INTEGER ::= 15
maxnoofEPLMNsPlusOne                    INTEGER ::= 16
maxnoofForbLACs                         INTEGER ::= 4096
maxnoofForbTACs                         INTEGER ::= 4096
maxNrOfIndividualS1ConnectionsToReset   INTEGER ::= 256
maxnoofCells                            INTEGER ::= 16
maxnoofTAIforWarning                    INTEGER ::= 65535
maxnoofCellID                           INTEGER ::= 65535
maxnoofEmergencyAreaID                  INTEGER ::= 65535
maxnoofCellinTAI                        INTEGER ::= 65535
maxnoofCellinEAI                        INTEGER ::= 65535
maxnoofeNBX2TLAs                        INTEGER ::= 2
maxnoofRATs                             INTEGER ::= 8
maxnoofGroupIDs                         INTEGER ::= 65535
maxnoofMMECs                            INTEGER ::= 256



-- **************************************************************
--
-- IEs
--
-- **************************************************************

id-MME-UE-S1AP-ID                           ProtocolIE-ID ::= 0
id-HandoverType                             ProtocolIE-ID ::= 1
id-Cause                                    ProtocolIE-ID ::= 2
id-SourceID                                 ProtocolIE-ID ::= 3
id-TargetID                                 ProtocolIE-ID ::= 4
id-eNB-UE-S1AP-ID                           ProtocolIE-ID ::= 8
id-E-RABSubjecttoDataForwardingList         ProtocolIE-ID ::= 12
id-E-RABtoReleaseListHOCmd                  ProtocolIE-ID ::= 13
id-E-RABDataForwardingItem                  ProtocolIE-ID ::= 14
id-E-RABReleaseItemBearerRelComp            ProtocolIE-ID ::= 15
id-E-RABToBeSetupListBearerSUReq            ProtocolIE-ID ::= 16
id-E-RABToBeSetupItemBearerSUReq            ProtocolIE-ID ::= 17
id-E-RABAdmittedList                        ProtocolIE-ID ::= 18
id-E-RABFailedToSetupListHOReqAck           ProtocolIE-ID ::= 19
id-E-RABAdmittedItem                        ProtocolIE-ID ::= 20
id-E-RABFailedtoSetupItemHOReqAck           ProtocolIE-ID ::= 21
id-E-RABToBeSwitchedDLList                  ProtocolIE-ID ::= 22
id-E-RABToBeSwitchedDLItem                  ProtocolIE-ID ::= 23
id-E-RABToBeSetupListCtxtSUReq              ProtocolIE-ID ::= 24
id-TraceActivation                          ProtocolIE-ID ::= 25
id-NAS-PDU                                  ProtocolIE-ID ::= 26
id-E-RABToBeSetupItemHOReq                  ProtocolIE-ID ::= 27
id-E-RABSetupListBearerSURes                ProtocolIE-ID ::= 28
id-E-RABFailedToSetupListBearerSURes        ProtocolIE-ID ::= 29
id-E-RABToBeModifiedListBearerModReq        ProtocolIE-ID ::= 30
id-E-RABModifyListBearerModRes              ProtocolIE-ID ::= 31
id-E-RABFailedToModifyList                  ProtocolIE-ID ::= 32
id-E-RABToBeReleasedList                    ProtocolIE-ID ::= 33
id-E-RABFailedToReleaseList                 ProtocolIE-ID ::= 34
id-E-RABItem                                ProtocolIE-ID ::= 35
id-E-RABToBeModifiedItemBearerModReq        ProtocolIE-ID ::= 36
id-E-RABModifyItemBearerModRes              ProtocolIE-ID ::= 37
id-E-RABReleaseItem                         ProtocolIE-ID ::= 38
id-E-RABSetupItemBearerSURes                ProtocolIE-ID ::= 39
id-SecurityContext                          ProtocolIE-ID ::= 40
id-HandoverRestrictionList                  ProtocolIE-ID ::= 41
id-UEPagingID                               ProtocolIE-ID ::= 43
id-pagingDRX                                ProtocolIE-ID ::= 44
id-TAIList                                  ProtocolIE-ID ::= 46
id-TAIItem                                  ProtocolIE-ID ::= 47
id-E-RABFailedToSetupListCtxtSURes          ProtocolIE-ID ::= 48
id-E-RABReleaseItemHOCmd                    ProtocolIE-ID ::= 49
id-E-RABSetupItemCtxtSURes                  ProtocolIE-ID ::= 50
id-E-RABSetupListCtxtSURes                  ProtocolIE-ID ::= 51
id-E-RABToBeSetupItemCtxtSUReq              ProtocolIE-ID ::= 52
id-E-RABToBeSetupListHOReq                  ProtocolIE-ID ::= 53
id-GERANtoLTEHOInformationRes                   ProtocolIE-ID ::= 55
id-UTRANtoLTEHOInformationRes                   ProtocolIE-ID ::= 57
id-CriticalityDiagnostics                       ProtocolIE-ID ::= 58
id-Global-ENB-ID                                ProtocolIE-ID ::= 59
id-eNBname                                      ProtocolIE-ID ::= 60
id-MMEname                                      ProtocolIE-ID ::= 61
id-ServedPLMNs                                  ProtocolIE-ID ::= 63
id-SupportedTAs                                 ProtocolIE-ID ::= 64
id-TimeToWait                                   ProtocolIE-ID ::= 65
id-uEaggregateMaximumBitrate                    ProtocolIE-ID ::= 66
id-TAI                                          ProtocolIE-ID ::= 67
id-E-RABReleaseListBearerRelComp                ProtocolIE-ID ::= 69
id-cdma2000PDU                                  ProtocolIE-ID ::= 70
id-cdma2000RATType                              ProtocolIE-ID ::= 71
id-cdma2000SectorID                             ProtocolIE-ID ::= 72
id-SecurityKey                                  ProtocolIE-ID ::= 73
id-UERadioCapability                            ProtocolIE-ID ::= 74
id-GUMMEI-ID                                    ProtocolIE-ID ::= 75
id-E-RABInformationListItem                     ProtocolIE-ID ::= 78
id-Direct-Forwarding-Path-Availability          ProtocolIE-ID ::= 79
id-UEIdentityIndexValue                         ProtocolIE-ID ::= 80
id-cdma2000HOStatus                             ProtocolIE-ID ::= 83
id-cdma2000HORequiredIndication                 ProtocolIE-ID ::= 84
id-E-UTRAN-Trace-ID                             ProtocolIE-ID ::= 86
id-RelativeMMECapacity                          ProtocolIE-ID ::= 87
id-SourceMME-UE-S1AP-ID                         ProtocolIE-ID ::= 88
id-Bearers-SubjectToStatusTransfer-Item         ProtocolIE-ID ::= 89
id-eNB-StatusTransfer-TransparentContainer      ProtocolIE-ID ::= 90
id-UE-associatedLogicalS1-ConnectionItem        ProtocolIE-ID ::= 91
id-ResetType                                    ProtocolIE-ID ::= 92
id-UE-associatedLogicalS1-ConnectionListResAck  ProtocolIE-ID ::= 93
id-E-RABToBeSwitchedULItem                      ProtocolIE-ID ::= 94
id-E-RABToBeSwitchedULList                      ProtocolIE-ID ::= 95
id-S-TMSI                                       ProtocolIE-ID ::= 96
id-cdma2000OneXRAND                             ProtocolIE-ID ::= 97
id-RequestType                                  ProtocolIE-ID ::= 98
id-UE-S1AP-IDs                                  ProtocolIE-ID ::= 99
id-EUTRAN-CGI                                   ProtocolIE-ID ::= 100
id-OverloadResponse                             ProtocolIE-ID ::= 101
id-cdma2000OneXSRVCCInfo                        ProtocolIE-ID ::= 102
id-E-RABFailedToBeReleasedList                  ProtocolIE-ID ::= 103
id-Source-ToTarget-TransparentContainer         ProtocolIE-ID ::= 104
id-ServedGUMMEIs                                ProtocolIE-ID ::= 105
id-SubscriberProfileIDforRFP                    ProtocolIE-ID ::= 106
id-UESecurityCapabilities                       ProtocolIE-ID ::= 107
id-CSFallbackIndicator                          ProtocolIE-ID ::= 108
id-CNDomain                                     ProtocolIE-ID ::= 109
id-E-RABReleasedList                            ProtocolIE-ID ::= 110
id-MessageIdentifier                            ProtocolIE-ID ::= 111
id-SerialNumber                                 ProtocolIE-ID ::= 112
id-WarningAreaList                              ProtocolIE-ID ::= 113
id-RepetitionPeriod                             ProtocolIE-ID ::= 114
id-NumberofBroadcastRequest                     ProtocolIE-ID ::= 115
id-WarningType                                  ProtocolIE-ID ::= 116
id-WarningSecurityInfo                          ProtocolIE-ID ::= 117
id-DataCodingScheme                             ProtocolIE-ID ::= 118
id-WarningMessageContents                       ProtocolIE-ID ::= 119
id-BroadcastCompletedAreaList                   ProtocolIE-ID ::= 120
id-Inter-SystemInformationTransferTypeEDT       ProtocolIE-ID ::= 121
id-Inter-SystemInformationTransferTypeMDT       ProtocolIE-ID ::= 122
id-Target-ToSource-TransparentContainer         ProtocolIE-ID ::= 123
id-SRVCCOperationPossible                       ProtocolIE-ID ::= 124
id-SRVCCHOIndication                            ProtocolIE-ID ::= 125
id-NAS-DownlinkCount                            ProtocolIE-ID ::= 126
id-CSG-Id                                       ProtocolIE-ID ::= 127
id-CSG-IdList                                   ProtocolIE-ID ::= 128
id-SONConfigurationTransferECT                  ProtocolIE-ID ::= 129
id-SONConfigurationTransferMCT                  ProtocolIE-ID ::= 130
id-TraceCollectionEntityIPAddress               ProtocolIE-ID ::= 131
id-MSClassmark2                                 ProtocolIE-ID ::= 132
id-MSClassmark3                                 ProtocolIE-ID ::= 133
id-RRC-Establishment-Cause                      ProtocolIE-ID ::= 134
id-NASSecurityParametersfromE-UTRAN             ProtocolIE-ID ::= 135
id-NASSecurityParameterstoE-UTRAN               ProtocolIE-ID ::= 136
id-DefaultPagingDRX                             ProtocolIE-ID ::= 137
id-Source-ToTarget-TransparentContainer-Secondary   ProtocolIE-ID ::= 138
id-Target-ToSource-TransparentContainer-Secondary   ProtocolIE-ID ::= 139
id-EUTRANRoundTripDelayEstimationInfo           ProtocolIE-ID ::= 140
id-BroadcastCancelledAreaList                   ProtocolIE-ID ::= 141
id-ConcurrentWarningMessageIndicator            ProtocolIE-ID ::= 142
id-Data-Forwarding-Not-Possible                 ProtocolIE-ID ::= 143
id-ExtendedRepetitionPeriod                     ProtocolIE-ID ::= 144
id-CellAccessMode                               ProtocolIE-ID ::= 145
id-CSGMembershipStatus                          ProtocolIE-ID ::= 146
id-LPPa-PDU                                     ProtocolIE-ID ::= 147
id-Routing-ID                                   ProtocolIE-ID ::= 148
id-Time-Synchronization-Info                    ProtocolIE-ID ::= 149
id-PS-ServiceNotAvailable                       ProtocolIE-ID ::= 150
id-RegisteredLAI                                ProtocolIE-ID ::= 159

END
